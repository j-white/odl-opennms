module opennms-impl {
    yang-version 1;
    namespace "urn:opendaylight:params:xml:ns:yang:opennms:impl";
    prefix "opennms-impl";

    import config { prefix config; revision-date 2013-04-05; }
    import opendaylight-md-sal-binding { prefix mdsal; revision-date 2013-10-28; }

    description
        "Service definition for opennms project";

    revision "2014-12-10" {
        description
            "Initial revision";
    }

    identity opennms {
        base config:module-type;
        config:java-name-prefix Opennms;
    }

    augment "/config:modules/config:module/config:configuration" {
        case opennms {
            when "/config:modules/config:module/config:type = 'opennms'";

     container data-broker {
        uses config:service-ref {
          refine type {
            mandatory true;
            config:required-identity mdsal:binding-async-data-broker;
          }
        }
      }

        }
    }
}
